package PhysicalPorts {
  // Physical interface types for data-center hardware

  port def EthernetPort;
  port def PowerPort;
  port def ManagementPort;
  port def CoolingPort;
  port def CpuFabricPort;
  port def MemoryBusPort;
  port def StorageBusPort;
}
